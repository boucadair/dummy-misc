module iana-bgp-ext-com-types {
  yang-version 1.1;
  namespace "urn:ietf:params:xml:ns:yang:iana-bgp-ext-com-types";
  prefix iana-bgp-ext-com-types;

  organization
    "Internet Assigned Numbers Authority (IANA)";

  contact
    "Internet Assigned Numbers Authority

     ICANN
     12025 Waterfront Drive, Suite 300
     Los Angeles, CA 90094

     Tel: +1 424 254 5300

     <mailto:iana@iana.org>";

  description
    "This YANG module translates IANA registry ASN-based BGP
     Extended Community types to YANG derived types.

     Copyright (c) 2025 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     The initial version of this YANG module is part of RFC XXXX; 
     see the RFC itself for full legal notices.
 
     // RFC Ed.: replace the IANA_FOO_URL and remove this note

     The latest version of this YANG module is available at
     <IANA_FOO_URL>.";

  reference
    "Border Gateway Protocol (BGP) Extended Communities
     (https://www.iana.org/assignments/bgp-extended-communities/)";

  revision 2025-06-30 {
    description
      "Current revision as of the revision date specified in the XML
       representation of the registry page.";
    reference
      "https://www.iana.org/assignments/bgp-extended-communities/
       bgp-extended-communities.xhtml#transitive
       https://www.iana.org/assignments/bgp-extended-communities/
       bgp-extended-communities.xhtml#non-transitive";
  }

  /* Typedefs */

  typedef bgp-ext-com-type-name {
    type enumeration {
      enum transitive-two-octet-as-specific {
        value 0;
        description
          "Transitive Two-Octet AS-Specific Extended Communities";
        reference
          "RFC7153";
      }
      enum transitive-four-octet-as-specific {
        value 2;
        description
          "Transitive Four-Octet AS-Specific Extended Communities";
        reference
          "RFC7153";
      }
      enum non-transitive-two-octet-as-specific {
        value 64;
        description
          "Non-Transitive Two-Octet AS-Specific Extended Communities";
        reference
          "RFC7153";
      }
      enum non-transitive-four-octet-as-specific {
        value 66;
        description
          "Non-Transitive Four-Octet AS-Specific Extended Communities";
        reference
          "RFC7153";
      }
    }
    description
      "This enumeration type defines mnemonic names and
       corresponding numeric values of BGP Extended Community
       types.";
    reference
      "RFC 7153: IANA Registries for BGP Extended Communities";
  }

  typedef bgp-ext-com-type {
    type union {
      type uint8;
      type bgp-ext-com-type-name;
    }
    description
      "This type allows reference to a BGP Extended Community
       type using either the assigned mnemonic name or the
       numeric protocol number value.";
  }
}
