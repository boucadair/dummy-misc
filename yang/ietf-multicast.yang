module ietf-multicast {
  yang-version 1.1;
  namespace "urn:ietf:params:xml:ns:yang:ietf-multicast";
  prefix multicast;

  import ietf-yang-types {
    prefix yang;
    reference
      "RFC 6991: Common YANG Data Types, Section 3";
  }
  import ietf-inet-types {
    prefix inet;
    reference
      "RFC 6991: Common YANG Data Types, Section 4";
  }
  import ietf-routing-types {
    prefix rt-types;
    reference
      "RFC 8294: Common YANG Data Types for the Routing Area";
  }
  import ietf-routing {
    prefix rt;
    reference
      "RFC 8349: A YANG Data Model for Routing Management
                 (NMDA Version)";
  }
  import ietf-te-types {
    prefix te-types;
    reference
      "RFC 8776: Common YANG Data Types for Traffic Engineering";
  }

  organization
    " IETF MBONED (MBONE Deployment) Working Group";
  contact
    "WG List:  <mailto:mboned@ietf.org>

     Author:   Zheng Zhang
               <mailto:zhang.zheng@zte.com.cn>
     Author:   Cui Wang
               <mailto:lindawangjoy@gmail.com>
     Author:   Ying Cheng
               <mailto:chengying10@chinaunicom.cn>
     Author:   Xufeng Liu
               <mailto:xufeng.liu.ietf@gmail.com>
     Author:   Mahesh Sivakumar
               <mailto:sivakumar.mahesh@gmail.com>";

  description
    "The module specifies the YANG definitions for multicast service
     management. This module covers the overlay, transport protocol
     used by a multicast flow. The underlay protocol is used as
     the transport layer building.

     Copyright (c) 2025 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     All revisions of IETF and IANA published modules can be found
     at the YANG Parameters registry group
     (https://www.iana.org/assignments/yang-parameters).

     This version of this YANG module is part of RFC XXXX; see
     the RFC itself for full legal notices.";

  revision 2025-05-06 {
    description
      "Initial revision.";
    reference
      "RFC XXXX: A YANG Data Model for Multicast Service Management";
  }

  /*
   * features
   */

  feature bier {
    description
      "Indicates support for BIER with multicast.";
    reference
      "RFC 8279: Multicast Using Bit Index Explicit Replication
                 (BIER)";
  }

  feature sr {
    description
      "Indicates support for Segment Routing (SR).";
    reference
      "RFC 8402: Segment Routing Architecture";
  }

  feature mldp {
    description
      "Indicates support for Multipoint Label Distribution
       Protocol (mLDP).";
    reference
      "RFC 6388: Label Distribution Protocol Extensions
                 for Point-to-Multipoint and 
                 Multipoint-to-Multipoint Label Switched
                 Paths";
  }

  feature p2mp-te {
    description
      "Indicates support for Resource Reservation Protocol
       Traffic Engineering (RSVP-TE) for Point-to-Multipoint
       (P2MP).";
    reference
      "RFC 4875: Extensions to Resource Reservation Protocol -
                 Traffic Engineering (RSVP-TE) for
                 Point-to-Multipoint TE Label Switched Paths
                 (LSPs)";
  }

  feature pim {
    description
      "Indicates support for Protocol Independent Multicast
       (PIM).";
    reference
      "RFC 7761: Protocol Independent Multicast - Sparse Mode
                 (PIM-SM): Protocol Specification (Revised)";
  }

  /*
   * Typedefs
   */

  typedef ip-multicast-source-address {
    type union {
      type enumeration {
        enum * {
          description
            "Any source IP address.";
        }
      }
      type inet:ipv4-address;
      type inet:ipv6-address;
    }
    description
      "Multicast source IP address type.";
  }

  typedef tree-sid {
    type union {
      type rt-types:mpls-label;
      type inet:ip-prefix;
    }
    description
      "The type of the Segment Identifier (SID) of a Replication
       segment is an SR-MPLS label or an SRv6 SID.

       The Replication-SID of the Replication segment of a P2MP tree
       instance.";
    reference
      "RFC 9524: Segment Routing Replication for Multipoint Service
                 Delivery";
  }

  /*
   * Identities
   */

  
  /* Med: this is not used in the module
  identity multicast-service {
    base rt:control-plane-protocol;
    description
      "Base identity for the multicast service.";
  }*/

  identity tunnel-encap-type {
    description
      "Base identity for the type of multicast flow tunnel
       encapsulation.";
  }

  identity tunnel-encap-vxlan {
    base tunnel-encap-type;
    description
      "Indicates Virtual eXtensible Local Area Network (VXLAN)
       encapsulation.";
    reference
      "RFC 7348: Virtual eXtensible Local Area Network (VXLAN):
                 A Framework for Overlaying Virtualized Layer 2
                 Networks over Layer 3 Networks";
  }

  identity tunnel-encap-nvgre {
    base tunnel-encap-type;
    description
      "Indicates Network Virtualization Using Generic Routing
       Encapsulation (NVRGE).";
    reference
      "RFC 7637: NVGRE: Network Virtualization Using Generic
                 Routing Encapsulation";
  }

  identity tunnel-encap-geneve {
    base tunnel-encap-type;
    description
      "Indicates Generic Network Virtualization Encapsulation
       (GENEVE) encapsulation.";
    reference
      "RFC 8926: Geneve: Generic Network Virtualization
                 Encapsulation";
  }

  identity overlay-type {
    description
      "Base identity for the type of multicast overlay.";
  }

  identity overlay-pim {
    base overlay-type;
    description
      "Indicates PIM as multicast overlay.";
    reference
      "RFC 7761: Protocol Independent Multicast - Sparse Mode
                 (PIM-SM): Protocol Specification (Revised)";
  }

  identity overlay-mld {
    base overlay-type;
    description
      "Indicates Multicast Listener Discovery (MLD) as multicast
       overlay.";
    reference
      "RFC 2710: Multicast Listener Discovery (MLD) for IPv6";
  }

  identity overlay-mld-snooping {
    base overlay-type;
    description
      "Indicates MLD-snooping as multicast overlay technology.";
    reference
      "RFC 4541: Considerations for Internet Group Management
                 Protocol (IGMP) and Multicast Listener
                 Discovery (MLD) Snooping Switches";
  }

  identity overlay-evpn {
    base overlay-type;
    description
      "Indicates Ethernet VPN (EVPN) as multicast overlay technology.";
    reference
      "RFC 7432: BGP MPLS-Based Ethernet VPN
       RFC 9572: Updates on EVPN BUM Procedures
       RFC 9624: EVPN Broadcast, Unknown Unicast, or Multicast
                 (BUM) Using Bit Index Explicit Replication (BIER)";
  }

  identity overlay-mvpn {
    base overlay-type;
    description
      "Indicates Multicast VPN (MVPN) as multicast overlay technology.";
    reference
      "RFC 6513: Multicast in MPLS/BGP IP VPNs
       RFC 7716: Global Table Multicast with BGP Multicast VPN
                 (BGP-MVPN) Procedures
       RFC 8556: Multicast VPN Using Bit Index Explicit Replication
                 (BIER)";
  }

  identity transport-type {
    description
      "Base identity for the multicast transport.";
  }

  identity transport-bier {
    base transport-type;
    description
      "Indicates Bit Index Explicit Replication (BIER) as multicast
       transport technology.";
    reference
      "RFC 8279: Multicast Using Bit Index Explicit Replication
                 (BIER)";
  }

  identity transport-bier-te {
    base transport-type;
    description
      "Indicates BIER-TE as multicast transport technology.";
    reference
      "RFC 9262: Traffic Engineering for Bit Index Explicit Replication
                 (BIER-TE)";
  }

  identity transport-mldp {
    base transport-type;
    description
      "Indicates mLDP as multicast transport technology.";
    reference
      "RFC 6388: Label Distribution Protocol Extensions
                 for Point-to-Multipoint and Multipoint-to-Multipoint
                 Label Switched Paths";
  }

  identity transport-rsvp-te-p2mp {
    base transport-type;
    description
      "Indicates P2MP TE as multicast transport technology.";
    reference
      "RFC 4875: Extensions to Resource Reservation Protocol
                 - Traffic Engineering (RSVP-TE) for Point-to-Multipoint
                 TE Label Switched Paths (LSPs).";
  }

  identity transport-sr-p2mp {
    base transport-type;
    description
      "Indicates SR as multicast transport technology.";
  }

  identity transport-pim {
    base transport-type;
    description
      "Indicates PIM as multicast transport technology.";
    reference
      "RFC 7761: Protocol Independent Multicast - Sparse Mode
                 (PIM-SM): Protocol Specification (Revised).";
  }

  identity underlay-type {
    description
      "Base identity for the multicast underlay.";
  }

  identity bgp {
    base underlay-type;
    description
      "Indicates BGP as underlay to build the multicast
       transport layer. For example, using BGP as BIER underlay.";
    reference
      "RFC 4271: A Border Gateway Protocol 4 (BGP-4)";
  }

  identity ospf {
    base underlay-type;
    description
      "Indicates OSPF as multicast underlay.
       For example, using OSPF as BIER underlay.";
    reference
      "RFC 8444: OSPFv2 Extensions for Bit Index Explicit Replication
                 (BIER)";
  }

  identity isis {
    base underlay-type;
    description
      "Indicates IS-IS as multicast underlay.
       For example, using IS-IS as BIER underlay.";
    reference
      "RFC 8401: Bit Index Explicit Replication (BIER) Support
                 via IS-IS";
  }

  identity babel {
    base underlay-type;
    description
      "Indicates BABEL as multicast underlay.
       For example, using BABEL as BIER underlay.";
    reference
      "RFC 8966: The Babel Routing Protocol";
  }

  identity rift {
    base underlay-type;
    description
      "Indicates Routing in Fat Trees (RIFT) as multicast underlay.
       For example, using RIFT as BIER underlay.";
    reference
      "RFC 9692: RIFT: Routing in Fat Trees";
  }

  identity event-type {
    description
      "Base identity for events of the multicast service.";
  }

  identity up {
    base event-type;
    description
      "Indicates that the multicast service is up and running.";
  }

  identity down {
    base event-type;
    description
      "Indicates that there is an issue with ingress or egress node,
       and node can not work properlay.";
  }

  identity protocol-enabled {
    base event-type;
    description
      "Indicates that the protocol that is used for multicast
       flows have been enabled.";
  }

  identity protocol-disabled {
    base event-type;
    description
      "Indicates that the protocol that is used by multicast
       flows have been disabled.";
  }

  identity bier-encapsulation {
    description
    "Base identity for BIER encapsulation.";
  }

  identity mpls {
    base bier-encapsulation;
    description
      "Indicates MPLS encapsulation for BIER.";
  }

  identity ipv6 {
    base bier-encapsulation;
    description
      "Indicates IPv6 encapsulation for BIER.";
  }

  identity ethernet {
    base bier-encapsulation;
      description
        "Indicates Ethernet encapsulation for BIER.";
  }

  /* Groupings */

  grouping general-multicast-key {
    description
      "The general multicast keys. They are used to differentiate
       multicast services.";
    leaf source-address {
      type ip-multicast-source-address;
      description
        "The IP source address of the multicast flow. The
         value set to '*' means that the receiver interests
         in all sources that relevant to one given group.";
    }
    leaf group-address {
      type rt-types:ip-multicast-group-address;
      mandatory true;
      description
        "The IP group address of multicast flow. This type
         represents a version-neutral IP multicast group
         address. The format of the textual representation
         implies the IP version.";
      reference
        "RFC 8294: Common YANG Data Types for the Routing Area";
    }
  }

  grouping optional-multicast-key {
    description
      "The optional multicast keys. They are used to differentiate
       multicast services.";
    leaf vpn-rd {
      type rt-types:route-distinguisher;
      description
        "A Route Distinguisher (RD) is used to differentiate
         routes from different MVPNs.";
      reference
        "RFC 8294: Common YANG Data Types for the Routing Area
         RFC 6513: Multicast in MPLS/BGP IP VPNs";
    }
    leaf mac-address {
      type yang:mac-address;
      description
        "The MAC address of flow. In the EVPN situation, the L2
         flow that is called BUM (Broadcast, Unknown Unicast, 
         Multicast) can be sent to other PEs that are in
         a same broadcast domain.";
      reference
        "RFC 6991: Common YANG Data Types
         RFC 7432: BGP MPLS-Based Ethernet VPN";
    }
    leaf vni-value {
      type uint32;
      description
        "The value of VXLAN network identifier, virtual subnet ID
         or virtual net identifier. This value and vni-type is used
         to indicate a specific virtual multicast service.";
    }
  }

  // multicast-key
  /* Med: Not used. check if this is needed 
  grouping encap-type {
    description
      "The encapsulation type used for BIER flow forwarding.
       This encapsulation acts as the inner encapsulation,
       as compared to the outer multicast-transport encapsulation.";
    choice encap-type {
      case mpls {
        description
          "The BIER forwarding depends on MPLS.";
        reference
          "RFC 8296: Encapsulation for Bit Index Explicit
                     Replication (BIER) in MPLS and Non-MPLS
                     Networks.";
      }
      case ethernet {
        description
          "The BIER forwarding depends on ethernet.";
        reference
          "RFC 8296: Encapsulation for Bit Index Explicit
                     Replication (BIER) in MPLS and Non-MPLS
                     Networks.";
      }
      case ipv6 {
        description
          "The BIER forwarding depends on IPv6.";
      }
      description
        "The encapsulation type in BIER.";
    }
  }*/

  grouping bier-key {
    description
      "The key parameters set for BIER/BIER TE forwarding.";
    reference
      "RFC 8279: Multicast Using Bit Index Explicit Replication
                 (BIER).";
    leaf sub-domain {
      type uint16;
      description
        "The subdomain ID that the multicast flow belongs to.";
    }
    leaf bitstringlength {
      type uint16;
      description
        "The BitStringLength used by BIER forwarding.";
    }
    leaf set-identifier {
      type uint16;
      description
        "The Set Identifier (SI) used by the multicast flow.";
    }
    leaf bier-encap-type {
      type identityref {
        base bier-encapsulation;
      }
      description
        "The BIER encapsulation that can be used in either MPLS
         networks or non-MPLS networks.";
    }
  }

  grouping transport-technology {
    description
      "The transport technology selected for the multicast service.
       For one specific multicast flow.";
    leaf type {
      type identityref {
        base transport-type;
      }
      description
        "Specifies the type of transport technology.";
    }
    choice transport-tech-type {
      description
        "Indicares the type of transport technology.";
      case bier {
        if-feature "bier";
        description
          "Using BIER as the transport technology.";
        reference
          "RFC 8296: Encapsulation for Bit Index Explicit
                     Replication (BIER) in MPLS and Non-MPLS
                     Networks";
        uses bier-key;
      }
      case bier-te {
        if-feature "bier";
        description
          "Using BIER-TE as the transport technology.";
        reference
          "RFC 9262: Tree Engineering for Bit Index Explicit
                     Replication (BIER-TE)";
        //uses bier-key;
        list bitstring {
          key "name";
          leaf name {
            type string;
            description
              "The name of the BitString.";
          }
          list bier-te-adj {
            key "adj-id";
            leaf adj-id {
              type uint16;
              description
                "The link adjacency ID used for BIER TE forwarding.";
            }
            description
              "The adjacencies ID used for BIER TE BitString
               encapsulation.";
          }
          description
            "The BitString name and detail used for BIER TE
             forwarding encapsulation. One or more BitStrings can be
             used for backup paths.";
        }
      }
      case mldp {
        if-feature "mldp";
        description
          "MLDP is used as the transport technology.";
        reference
          "RFC 6388: Label Distribution Protocol Extensions
                     for Point-to-Multipoint and Multipoint-to-Multipoint
                     Label Switched Paths";
      }
      case rsvp-te-p2mp {
        if-feature "p2mp-te";
        description
          "RSVP TE P2MP is used as the transport technology.";
        reference
          "RFC 4875: Extensions to Resource Reservation Protocol -
                     Traffic Engineering (RSVP-TE) for Point-to-Multipoint
                     TE Label Switched Paths (LSPs)
           RFC 8776: Common YANG Data Types for Traffic Engineering";
        leaf template-name {
          type te-types:te-template-name;
          description
            "A type for the name of a TE node template or TE link
             template.";
        }
      }
      case pim {
        if-feature "pim";
        description
          "PIM is used as the transport technology.";
        reference
          "RFC 7761: Protocol Independent Multicast - Sparse Mode
                     (PIM-SM): Protocol Specification (Revised)";
        uses pim;
      }
    }
  }

  // Underlay Technology

  grouping underlay-technology {
    description
      "The underlay technology selected for the transport layer.
       The underlay technology has no straight relationship with
       the multicast overlay, it is used for transport path
       building, for example, BIER forwarding path building.";
    leaf type {
      type identityref {
        base underlay-type;
      }
      description
        "Specifies the type of underlay technology.";
    }
    choice underlay-technology-type {
      description
        "A choice for the underlay type.";
      case ospf {
        description
          "Using OSPF as the underlay technology.
           If OSPF  supports multiple topology feature,
           the associated topology name may be assigned.
           In case the topology name is assigned, the specific
           OSPF topology is used for underly to building the
           transport layer.";
        reference
          "RFC 4915: Multi-Topology Routing
           RFC 9129: YANG Data Model for the OSPF Protocol";
        leaf topology-id {
          type uint8;
          description
            "The MT-ID for the topology enabled in OSPF protocol";
        }
      }
      case isis {
        description
          "Using IS-IS as the underlay technology.
           If IS-IS protocol supports multiple topology feature,
           the associated topology name may be assigned.
           In case the topology name is assigned, the specific
           IS-IS topology is used for underly to building the
           transport layer.";
        reference
          "RFC 5120: M-IS-IS: Multi Topology Routing in IS-IS
           RFC 9130: YANG Data Model for the IS-IS Protocol";
      }
      case pim {
        description
          "Using PIM as the underlay technology.";
        reference
          "RFC 7761: Protocol Independent Multicast - Sparse Mode
                     (PIM-SM): Protocol Specification (Revised)";
        uses pim;
      }
    }
  }

  // Underlay Technology

  /*overlay*/

  grouping overlay-technology {
    container dynamic-overlay {
      leaf type {
        type identityref {
          base overlay-type;
        }
        description
          "Indicares the type of overlay technology.";
      }
      choice overlay-technology-type {
        description
          "Choice for the overlay type.";
        case evpn {
          description
            "EVPN is used for multicast overlay.";
          reference
            "RFC 7432: BGP MPLS-Based Ethernet VPN
             RFC 9624: EVPN Broadcast, Unknown Unicast, or
                       Multicast (BUM) Using Bit Index Explicit
                       Replication (BIER)";
        }
        case mld {
          description
            "MLD/IGMP can be used as multicast overlay
             when BIER is used as transport technology.";
          leaf mld-instance-group {
            type rt-types:ip-multicast-group-address;
            description
              "The multicast address used for multiple MLD instance
               support.";
          }
        }
        case mld-snooping {
          description
            "MLD/IGMP snooping can be used as multicast overlay
             when BIER is used as transport technology.";
          reference
            "RFC 9166: A YANG Data Model for Internet Group
                       Management Protocol (IGMP) and Multicast Listener
                       Discovery (MLD) Snooping";
          leaf mld-snooping-group {
            type rt-types:ip-multicast-group-address;
            description
              "The multicast address used for MLD-snooping.";
          }
        }
        case mvpn {
          description
            "MVPN technology is used for multicast overlay.
             The global table multicast can also be achieved.";
          reference
            "RFC 6513: Multicast in MPLS/BGP IP VPNs
             RFC 7716: Global Table Multicast with BGP Multicast VPN
                       (BGP-MVPN) Procedures
             RFC 8556: Multicast VPN Using Bit Index Explicit
                       Replication (BIER)";
        }
        case pim {
          description
            "PIM can be used as multicast overlay
             when BIER is used as transport technology.";
          reference
            "RFC 7761: Protocol Independent Multicast - Sparse Mode
                       (PIM-SM): Protocol Specification (Revised)";
        }
      }
      description
        "The dynamic overlay technologies and associated parameter
         that may be set.";
    }
    description
      "The overlay technology used for multicast service.";
  }

  // overlay Technology
  /*transport*/

  grouping pim {
    description
      "The required information of pim transportion.";
    leaf source-address {
      type ip-multicast-source-address;
      description
        "The IP source address of the multicast flow. The
         value set to * means that the receiver interests
         in all source that relevant to one given group.";
    }
    leaf group-address {
      type rt-types:ip-multicast-group-address;
      mandatory true;
      description
        "The IP group address of multicast flow. This
         type represents a version-neutral IP multicast group
         address. The format of the textual representation
         implies the IP version.";
    }
    reference
      "RFC 7761: Protocol Independent Multicast - Sparse Mode
                 (PIM-SM): Protocol Specification (Revised).";
  }

  /*
   * Main container
   */ 

  container multicast-service {
    description
      "The model of multicast YANG data. Include keys, overlay,
       transport and underlay.";
    list multicast-keys {
      key "source-address group-address";
      uses general-multicast-key;
      uses optional-multicast-key;
      container multicast-overlay {
        description
          "The overlay information of multicast service.
           Overlay technology is used to exchange multicast
           flows information. Overlay technology may not be
           used in SDN controlled situation. Different overlay
           technologies can be chosen according to different
           deploy consideration.";
        leaf vni-type {
          type identityref {
            base tunnel-encap-type;
          }
          description
            "The encapsulated type for the multicast flow,
             it is used to carry the virtual network identifier
             for the multicast service.
             When this type is set, the associated vni-value
             MUST be set.";
        }
        container ingress-egress {
          description
            "The ingress and egress nodes address collection.
             The ingress node may use the egress nodes set
             directly to encapsulate the multicast flow by
             transport technology.";
          leaf-list ingress-nodes {
            type inet:ip-address;
            description
              "The ip address of ingress node for one or more
               multicast flow. Or the ingress node of MVPN,
               EVPN and BIER.
               In MVPN, this is the address of ingress
               PE; in BIER, this is the BFR-prefix of BFIR.
               Two or more ingress nodes may exist for the
               redundant ingress node protection.";
          }
          leaf-list egress-nodes {
            type inet:ip-address;
            description
              "The ip address of egress nodes for the multicast flow.
               Or the egress node of MVPN, EVPN and BIER.
               In MVPN, this is the address of egress PE;
               in BIER, this is the BFR-prefix of BFER.";
          }
        }
        container bier-ids {
          if-feature "bier";
          description
            "The BFR-ids of ingress and egress BIER nodes for
             one or more multicast flows. This overlay is used
             with BIER transport technology. The egress nodes
             set can be used to encapsulate the multicast flow
             directly in the ingress node.";
          reference
            "RFC 8279: Multicast Using Bit Index Explicit
                       Replication (BIER)";
          leaf sub-domain {
            type uint16;
            description
              "The sub-domain that this multicast flow belongs to.";
          }
          leaf-list ingress-nodes {
            type uint16;
            description
              "The BFR-ID of the ingress node.";
          }
          leaf-list egress-nodes {
            type uint16;
            description
              "The BFR-ID of the egress node.";
          }
        }
        uses overlay-technology;
      }
      container multicast-transport {
        description
          "The transportion of multicast service. Transport
           protocol is responsible for delivering multicast
           flows from ingress nodes to egress nodes with or
           without specific encapsulation. Different transport
           technology can be chosen according to different
           deploy consideration. Once a transport technology
           is chosen, associated protocol should be triggered
           to run.";
        uses transport-technology;
      }
      container multicast-underlay {
        description
          "The underlay of multicast service. Underlay protocol
           is used to build transport layer. Underlay protocol
           need not be assigned in ordinary network since
           existed underlay protocol fits well, but it can be
           assigned in particular networks for better
           controll. Once an underlay technology is chosen,
           associated protocol should be triggered to run.";
        uses underlay-technology;
      }
      description
        "The structure of multicast service. Include keys,
         overlay, transport, and underlay.";
    }
  }

  /*
   * Notifications
   */ 

  notification ingress-egress-event {
    leaf event-type {
      type identityref {
        base event-type;
      }
      description
        "Reports the event type.";
    }
    container multicast-key {
      uses general-multicast-key;
      uses optional-multicast-key;
      description
        "The associated multicast keys that are influenced by
         ingress or egress node failure.";
    }
    uses overlay-technology;
    container transport-technology {
      description
        "The modules can be used to forward multicast flows.";
      uses transport-technology;
    }
    container underlay-technology {
      description
        "There is something wrong with the module which is
         used to build multicast transport layer.";
      uses underlay-technology;
    }
    description
      "Notification events for the ingress or egress nodes. Like
       node failure, overlay/transport/underlay module
       loading/unloading. And the potential failure about some
       multicast flows and associated
       overlay/transport/underlay technologies.";
  }
}
