module ietf-pauline-test {
  yang-version 1.1;
  namespace "urn:ietf:params:xml:ns:yang:ietf-pauline-test";
  prefix pauline-test;

  organization
    "xxx";
  contact
    "WG Web:   <https://datatracker.ietf.org/wg/xx/>
     WG List:  <mailto:xx@ietf.org>

     Author:    xxx
                <mailto:xx@xx.com>";
  description
    "The YANG module defines xxxx.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry
     (https://www.iana.org/assignments/yang-parameters).

     This version of this YANG module is part of RFC XXXX; see
     the RFC itself for full legal notices.";

  revision 2025-04-03 {
    description
      "Initial revision.";
    reference "";
  }

  /* Identities */

  identity premier-id {
    description
      "Base identity for xxx.";
  }

  identity rouge {
    base premier-id;
    description
      "xxx.";
  }

  identity vert {
    base premier-id;
    description
      "xxx.";
  }

  identity deuxieme-id {
    description
      "Base identity for xxx.";
  }

  identity rouge-2 {
    base deuxieme-id;
    description
      "xxx.";
  }

  identity vert-2 {
    base deuxieme-id;
    description "xxx.";
  }

  container premier-nom {
    description
      "xxx.";
    container premier-nom {
      description "x.";
    }
    leaf-list deuxieme-nom {
       type identityref {
          base deuxieme-id;
       }
      description  "xxx.";
   }
  }
}
