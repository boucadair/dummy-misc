module ietf-sch-usage-1 {
  yang-version 1.1;
  namespace "http://example.com/example-sch-usage-8";
  prefix "ex-schu-8";

  organization "Example, Inc.";
  contact "Support at example.com";
  description "An example.";

  revision "2026-02-20" {
    description "Initial version.";
    reference
      "RFC 9922: A YANG Data Model for Scheduling.";
  }

  container icalendar-recurrence {
    description "A description.";
    uses schedule:icalendar-recurrence {
      description "A description.";
      refine workweek-start {
        default monday;
      }
    }
  }
}
