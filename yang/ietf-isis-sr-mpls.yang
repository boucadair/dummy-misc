module ietf-isis-sr-mpls {
  yang-version 1.1;
  namespace "urn:ietf:params:xml:ns:yang:ietf-isis-sr-mpls";
  prefix isis-sr-mpls;

  import ietf-routing {
    prefix rt;
    reference
      "RFC 8349: A YANG Data Model for Routing
                 Management (NMDA Version)";
  }
  import ietf-inet-types {
    prefix inet;
    reference
      "RFC 6991: Common YANG Data Types";
  }
  import ietf-segment-routing-common {
    prefix sr-cmn;
    reference
      "RFC 9020: YANG Data Model for Segment Routing";
  }
  import ietf-segment-routing-mpls {
    prefix sr-mpls;
    reference
      "RFC 9020: YANG Data Model for Segment Routing";
  }
  import ietf-isis {
    prefix isis;
    reference
      "RFC 9130: YANG Data Model for IS-IS Protocol";
  }
  import iana-routing-types {
    prefix iana-rt-types;
    reference
      "RFC 8294: Common YANG Data Types for the Routing Area";
  }
  import ietf-routing-types {
    prefix rt-types;
    reference
      "RFC 8294: Common YANG Data Types for the Routing Area";
  }

  organization
    "IETF LSR - Link State Routing Working Group";
  contact
    "WG Web:   <https://datatracker.ietf.org/wg/lsr/>
     WG List:  <mailto:lsr@ietf.org>

     Author:    Stephane Litkowski
                <mailto:slitkows.ietf@gmail.com>
     Author:    Yingzhen Qu
                <mailto:yingzhen.ietf@gmail.com>
     Author:    Acee Lindem
                <mailto:acee.ietf@gmail.com>
     Author:    Pushpasis Sarkar
                <mailto:pushpasis.ietf@gmail.com>
     Author:    Ing-Wher Chen
                <mailto:ingwherchen@mitre.org>
     Author:    Jeff Tantsura
                <mailto:jefftant.ietf@gmail.com>";
  description
    "The YANG module defines the generic configuration and
     operational state for Segment Routing (SR) IS-IS extensions
     for the MPLS data plane, which is common across all of the
     vendor implementations.

     This YANG model conforms to the Network Management
     Datastore Architecture (NMDA) as described in RFC 8342.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry
     (https://www.iana.org/assignments/yang-parameters).

     This version of this YANG module is part of RFC XXXX; see
     the RFC itself for full legal notices.";

  revision 2025-01-29 {
    description
      "Initial revision.";
    reference
      "RFC XXXX: A YANG Data Model for IS-IS Segment Routing for the
                 MPLS Data Plane";
  }

  /* Identities */

  identity sr-capability {
    description
      "Base identity for IS-IS SR-Capabilities sub-TLV flags.";
    reference
      "RFC 8667: IS-IS Extensions for Segment Routing, Section 3";
  }

  identity mpls-ipv4 {
    base sr-capability;
    description
      "Indicates that the router is capable of processing
       SR-MPLS-encapsulated IPv4 packets on all interfaces.";
    reference
      "RFC 8667: IS-IS Extensions for Segment Routing, Section 3.1";
  }

  identity mpls-ipv6 {
    base sr-capability;
    description
      "Indicates that the router is capable of processing
       SR-MPLS-encapsulated IPv6 packets on all interfaces.";
    reference
      "RFC 8667: IS-IS Extensions for Segment Routing, Section 3.1";
  }

  identity prefix-sid-flag {
    description
      "Base identity for Prefix-SID sub-TLV flags.";
    reference
      "RFC 8667: IS-IS Extensions for Segment Routing, Section 2.1";
  }

  identity r-flag {
    base prefix-sid-flag;
    description
      "Re-advertisement Flag.";
    reference
      "RFC 8667: IS-IS Extensions for Segment Routing, Section 2.1.1.2";
  }

  identity n-flag {
    base prefix-sid-flag;
    description
      "Node-SID Flag.";
    reference
      "RFC 8667: IS-IS Extensions for Segment Routing, Section 2.1.1.2";
  }

  identity p-flag {
    base prefix-sid-flag;
    description
      "No Penultimate Hop-Popping (No-PHP) Flag.";
    reference
      "RFC 8667: IS-IS Extensions for Segment Routing, Section 2.1.1.3";
  }

  identity e-flag {
    base prefix-sid-flag;
    description
      "Explicit NULL Flag.";
    reference
      "RFC 8667: IS-IS Extensions for Segment Routing, Section 2.1.1.3";
  }

  identity v-flag {
    base prefix-sid-flag;
    description
      "Value Flag.";
    reference
      "RFC 8667: IS-IS Extensions for Segment Routing, Section 2.1.1.1";
  }

  identity l-flag {
    base prefix-sid-flag;
    description
      "Local Flag.";
    reference
      "RFC 8667: IS-IS Extensions for Segment Routing, Section 2.1.1.1";
  }

  identity adj-sid-flag {
    description
      "Base identity for Adj-SID sub-TLV flags.";
    reference
      "RFC 8667: IS-IS Extensions for Segment Routing, Section 2.2";
  }

  identity f-flag {
    base adj-sid-flag;
    description
      "Address-Family flag.";
    reference
      "RFC 8667: IS-IS Extensions for Segment Routing, Section 2.2";
  }

  identity b-flag {
    base adj-sid-flag;
    description
      "Backup flag.";
    reference
      "RFC 8667: IS-IS Extensions for Segment Routing, Section 2.2";
  }

  identity vi-flag {
    base adj-sid-flag;
    description
      "Value/Index flag. Corresponds to the V-Flag.";
    reference
      "RFC 8667: IS-IS Extensions for Segment Routing, Section 2.2";
  }

  identity lo-flag {
    base adj-sid-flag;
    description
      "Local flag. Corresponds to the Adj-SID L-Flag.";
    reference
      "RFC 8667: IS-IS Extensions for Segment Routing, Section 2.2";
  }

  identity s-flag {
    base adj-sid-flag;
    description
      "Group flag.";
    reference
      "RFC 8667: IS-IS Extensions for Segment Routing, Section 2.2";
  }

  identity pe-flag {
    base adj-sid-flag;
    description
      "Persistent flag. Corresponds to the Adj-SID P-Flag.";
    reference
      "RFC 8667: IS-IS Extensions for Segment Routing, Section 2.2";
  }

  identity sid-binding-flag {
    description
      "Base identity for SID binding TLV flags.";
    reference
      "RFC 8667: IS-IS Extensions for Segment Routing, Section 2.4";
  }

  identity af-flag {
    base sid-binding-flag;
    description
      "Address-Family flag. Corresponds to the SID/Label Binding
       F-Flag.";
    reference
      "RFC 8667: IS-IS Extensions for Segment Routing, Section 2.4";
  }

  identity m-flag {
    base sid-binding-flag;
    description
      "Mirror Context flag.";
    reference
      "RFC 8667: IS-IS Extensions for Segment Routing, Section 2.4";
  }

  identity sf-flag {
    base sid-binding-flag;
    description
      "Corresponds to the SID/Label Binding S-Flag. Indicates that
       the SID/Label Binding TLV should be flooded across the entire
       routing domain.";
    reference
      "RFC 8667: IS-IS Extensions for Segment Routing, Section 2.4";
  }

  identity d-flag {
    base sid-binding-flag;
    description
      "Leaking flag.";
    reference
      "RFC 8667: IS-IS Extensions for Segment Routing, Section 2.4";
  }

  identity a-flag {
    base sid-binding-flag;
    description
      "Attached flag.";
    reference
      "RFC 8667: IS-IS Extensions for Segment Routing, Section 2.4";
  }

  // Med: Features should be before identities. 
  // Med: You may run "pyang -f yang --yang-canonical"   
  /* Features */

  feature remote-lfa-sr {
    description
      "Enhances rLFA to use SR path.";
    reference
      "RFC 8102: Remote-LFA Node Protection and Manageability";
  }

  feature ti-lfa {
    description
      "Topology-Independent Loop-Free Alternate (TI-LFA)
       computation using segment routing.";
    reference
      "RFC IIII: Topology-Independent Fast Reroute using Segment
                 Routing";
     //RFC Editor: Please replace IIII with the RFC number
     //assigned to draft-ietf-rtgwg-segment-routing-ti-lfa
  }

  /* Groupings */

  grouping sid-sub-tlv {
    description
      "SID/Label sub-TLV grouping.";
    reference
      "RFC 8667: IS-IS Extensions for Segment Routing, Section 2.3";
    container sid-sub-tlv {
      description
        "Used to advertise the SID/Label associated with a
         prefix or adjacency.";
      //Med: A type would be better instead fo inferring its from the length
      leaf length {
        type uint8;
        description
          "Length of the SID value. YANG model specification
           is necessary since it dictates the semantics of the
           SID.";
      }
      leaf sid {
        type uint32;
        description
          "Segment Identifier (SID). A 20-bit label or 32-bit SID.
           If the length is set to 3, then the 20 rightmost bits
           represent an MPLS label. If the length is set to 4, then
           the value is a 32-bit index.";
      }
    }
  }

  grouping sr-capability {
    description
      "SR capability grouping.";
    reference
      "RFC 8667: IS-IS Extensions for Segment Routing, Section 3";
    container sr-capability {
      description
        "Segment Routing capability.";
      //Med: sr-capability/sr-capability may question why we need two layers
      //Med: No need to repeat the parent prefix
      container capability {
        //Med: No need to repeat the parent prefix
        //Med: use singular per guidelines
        leaf-list flag {
          type identityref {
            base sr-capability;
          }
          description
            "SR Capability sub-TLV flags.";
        }
        description
          "SR Capability Flags.";
      }
      container global-blocks {
        description
          "Segment Routing Global Blocks (SRGB).";
        list global-block {
          description
            "Segment Routing Global Block.";
          leaf range-size {
            type uint32;
            description
              "The SID range.";
          }
          uses sid-sub-tlv;
        }
      }
    }
  }

  grouping sr-algorithm {
    description
      "SR algorithm grouping.";
    container sr-algorithms {
      description
        "All SR algorithms.";
      //Med: No need to repeat the prefix of the parent node
      leaf-list algorithm {
        type identityref {
          base sr-cmn:prefix-sid-algorithm;
        }
        description
          "The SR algorithms that the router is currently
           using.";
      }
    }
  }

  grouping srlb {
    description
      "SR Local Block grouping.";
    reference
      "RFC 8667: IS-IS Extensions for Segment Routing, Section 3.3";
    container local-blocks {
      description
        "List of SRLBs.";
      //Med: No need to repeat the prefix of the parent node
      list block {
        description
          "Segment Routing Local Block.";
        leaf range-size {
          type rt-types:uint24;
          description
            "The SID range.";
        }
        uses sid-sub-tlv;
      }
    }
  }

  grouping srms-preference {
    description
      "The Segment Routing Mapping Server (SRMS) preference
       TLV is used to advertise a preference associated with
       the node that acts as an SRMS.";
    reference
      "RFC 8667: IS-IS Extensions for Segment Routing, Section 3.4
       RFC 8661: Segment Routing MPLS Interworking with LDP,
                 Section 3.2.1";
    container srms-preference {
      description
        "SRMS Preference.";
      leaf preference {
        type uint8;
        description
          "SRMS preference, value from 0 to 255 with
           255 being the most preferred.";
      //Med: Add a pointer to justify why 255 is indicated as such
      reference
        "RFC 8661: Segment Routing MPLS Interworking with LDP,
                   Section 3.2.3";
      }
    }
  }

  grouping adjacency-state {
    description
      "This grouping extends adjacency state.";
    list adjacency-sid {
      key "value";
      config false;
      //Med: Consider expanding the description
      leaf value {
        type uint32;
        description
          "Value of the Adj-SID.";
      }
      leaf address-family {
        type iana-rt-types:address-family;
        description
          "Address-Family associated with the SID.";
      }
      leaf weight {
        type uint8;
        description
          "Weight associated with the adjacency SID.";
      }
      leaf protection-requested {
        type boolean;
        description
          "Describes whether the adjacency SID must be protected.
           It is protected, if set to 'true'.";
      }
      description
        "List of adjacency SIDs.";
    }
  }

  grouping prefix-sid-sub-tlv {
    description
      "This grouping defines segment routing prefix segment
       identifier (prefix-sid) sub-TLV.";
    reference
      "RFC 8667: IS-IS Extensions for Segment Routing, Section 2.1";
    container prefix-sid-sub-tlvs {
      description
        "Prefix-SID sub-TLVs.";
      //Med: no need to repeat the prefix of the parent node
      list prefix-sid {
        key "sid";
        container flags {
          //Med: Use singular per the 8407bis guidance.
          leaf-list flag {
            type identityref {
              base prefix-sid-flag;
            }
            description
              "Prefix SID sub-TLV flags.";
          }
          description
            "Describes flags associated with the SID.";
        }
        leaf algorithm {
          type identityref {
            base sr-cmn:prefix-sid-algorithm;
          }
          description
            "Algorithm to be used for path computation.";
        }
        leaf sid {
          type uint32;
          description
            "Value of the prefix-SID.";
        }
        description
          "List of prefix-sid sub-TLVs.";
      }
    }
  }

  grouping adjacency-segment-id {
    description
      "This grouping defines SR extensions for adjacencies.";
    list adj-sid-list {
      key "sid";
      //Med: rename the node
      container flags {
        //Med: Use singular per 8407bis guidance.
        leaf-list flag {
          type identityref {
            base adj-sid-flag;
          }
          description
            "Adj-SID sub-TLV flags list.";
        }
        description
          "Adj-SID sub-TLV flags.";
      }
      leaf weight {
        type uint8;
        description
          "The value represents the weight of the Adj-SID
           for the purpose of load balancing.";
      }
      leaf neighbor-id {
        type isis:system-id;
        description
          "Describes the system ID of the neighbor
           associated with the SID value. This is only
           used on LAN adjacencies.";
      }
      leaf sid {
        type uint32;
        description
          "Value of the Adj-SID.";
      }
      description
        "List of segments.";
    }
  }

  grouping sid-binding-tlv {
    leaf prefix {
      type inet:ip-prefix;
      description
        "The prefix represents the Forwarding Equivalence
         Class (FEC) at the tail end of the advertised path.";
    }
    leaf range {
      type uint16;
      description
        "Specifies a range of addresses and their associated
         Prefix-SIDs.";
    }
    //Med: Use consistent naming
    container flags {
      //Med: Use singular
      leaf-list flag {
        type identityref {
          base sid-binding-flag;
        }
        description
          "SID Binding TLV flags.";
      }
      description
        "Binding TLV flags.";
    }
    //Med: Use singular
    //Med: No need to reason with TLV for managing the functionality
    //Med: Do we need the tree levels prefix-sid-sub-tlvs/prefix-sid-sub-tlvs/prefix-sid-sub-tlv?
    list prefix-sid {
      uses prefix-sid-sub-tlv;
      description
        "List of Prefix-SID sub-TLVs.";
      reference
        "RFC 8667: IS-IS Extensions for Segment Routing,
                   Section 2.4.4";
    }
    //Med: Use singular
    //Med: No need to reason with TLV for managing the functionality
    list sid {
      uses sid-sub-tlv;
      description
        "List of Prefix-SIDs.";
      reference
        "RFC 8667: IS-IS Extensions for Segment Routing,
                   Section 2.4.5";
    }
    uses isis:unknown-tlvs;
    description
      "SID/Label binding TLV, type 149.";
    reference
      "RFC 8667: IS-IS Extensions for Segment Routing,
                 Section 2.4";
  }

  //Med: This can be used for reporting as well :-) Please rename.
  /* Configuration */

  augment "/rt:routing"
        + "/rt:control-plane-protocols/rt:control-plane-protocol"
        + "/isis:isis" {
    when "derived-from-or-self(../rt:type, 'isis:isis')" {
      description
        "This augments IS-IS routing protocol structure, when
         used.";
    }
    description
      "This augments IS-IS protocol configuration with SR for
       the MPLS data plane.";
    uses sr-mpls:sr-control-plane;
    container protocol-srgb {
      if-feature "sr-mpls:protocol-srgb";
      uses sr-cmn:srgb;
      description
        "Per-protocol Segment Routing Global Block (SRGB).";
      reference
        "RFC 8402: Segment Routing Architecture, Section 2";
    }
  }

  augment "/rt:routing"
        + "/rt:control-plane-protocols/rt:control-plane-protocol"
        + "/isis:isis/isis:interfaces/isis:interface" {
    when "derived-from-or-self(../../../rt:type, 'isis:isis')" {
      description
        "This augments ISIS routing protocol structure, when used.";
    }
    description
      "This augments ISIS protocol configuration structure with SR
       data nodes.";
    uses sr-mpls:igp-interface {
      augment "segment-routing/adjacency-sid/adj-sids" {
        when "../../../isis:interface-type = 'broadcast'" {
          description
            "This augments broadcast interface.";
        }
        description
          "This augments LAN interface Adj-SID with system-id.";
        leaf neighbor-system-id {
          type isis:system-id;
          mandatory true;
          description
            "Neighbor system ID.";
        }
      }
    }
  }

  augment "/rt:routing"
        + "/rt:control-plane-protocols/rt:control-plane-protocol"
        + "/isis:isis/isis:interfaces/isis:interface"
        + "/isis:fast-reroute/isis:lfa" {
    when "derived-from-or-self(../../../../../rt:type,"
       + "'isis:isis')" {
      description
        "This augments ISIS routing protocol structure, when used.";
    }
    description
      "This augments IS-IS interface IP FRR with TI-LFA.";
    container ti-lfa {
      if-feature "ti-lfa";
      leaf enabled {
        type boolean;
        default "false";
        description
          "Enables TI-LFA computation, if set to 'true'.";
      }
      container selection-tie-breakers {
        container node-protection {
          presence "Presence of container enables the node
                    protection tie-breaker";
          leaf priority {
            type uint8;
            default "128";
            description
              "Priority for node protection tie-breaker with
               a lower priority being more preferred.";
          }
          description
            "Enables node protection as a TI-LFA path
             selection tie-breaker. A path providing node
             protection will be selected over one that
             doesn't provide node protection.";
        }
        container srlg-disjoint {
          presence "Presence of container enables the SRLG
                    disjoint tie-breaker";
          leaf priority {
            type uint8;
            default "128";
            description
              "Priority for SRLG disjoint tie-breaker with
               a lower priority being more preferred.";
          }
          description
            "Enable Shared Resource Link Group (SRLG)
             disjoint as a TI-LFA path selection tie-breaker.
             A path providing node a disjoint path for SRLG
             links from the primary path will be selected over
             one that doesn't provide an SRLG disjoint path.";
        }
        description
          "Configures path selection tie-breakers and their
           respective priorities for the TI-LFA computation.";
      }
      description
        "TI-LFA support.";
    }
  }

  augment "/rt:routing"
        + "/rt:control-plane-protocols/rt:control-plane-protocol"
        + "/isis:isis/isis:interfaces/isis:interface"
        + "/isis:fast-reroute/isis:lfa/isis:level-1" {
    when "derived-from-or-self(../../../../../../rt:type,"
       + "'isis:isis')" {
      description
        "This augments IS-IS routing protocol structure, when used.";
    }
    description
      "This augments IS-IS interface level-1 IP FRR with TI-LFA.";
    container ti-lfa {
      if-feature "ti-lfa";
      leaf enabled {
        type boolean;
        default "false";
        description
          "Enables TI-LFA computation.";
      }
      description
        "TI-LFA configuration.";
    }
  }

  augment "/rt:routing"
        + "/rt:control-plane-protocols/rt:control-plane-protocol"
        + "/isis:isis/isis:interfaces/isis:interface"
        + "/isis:fast-reroute/isis:lfa/isis:level-2" {
    when "derived-from-or-self(../../../../../../rt:type,"
       + "'isis:isis')" {
      description
        "This augments IS-IS routing protocol structure, when used.";
    }
    description
      "This augments IS-IS IP interface level-2 FRR with TI-LFA.";
    container ti-lfa {
      if-feature "ti-lfa";
      leaf enabled {
        type boolean;
        default "false";
        description
          "Enables TI-LFA computation, if set to 'true'.";
      }
      description
        "TI-LFA configuration.";
    }
  }

  augment "/rt:routing"
        + "/rt:control-plane-protocols/rt:control-plane-protocol"
        + "/isis:isis/isis:interfaces/isis:interface"
        + "/isis:fast-reroute/isis:lfa/isis:remote-lfa" {
    when "derived-from-or-self(../../../../../../rt:type,"
       + "'isis:isis')" {
      description
        "This augments IS-IS routing protocol structure, when used.";
    }
    description
      "This augments IS-IS rLFA structure with use of SR path.";
    leaf use-segment-routing-path {
      if-feature "remote-lfa-sr";
      type boolean;
      default "false";
      description
        "Force remote LFA to use an SR path instead of the LDP
         path. The value of this leaf is in effect only when
         rLFA is enabled."; 
         //Med: The use of the feature means this is supported not
         //Med: enabled. Please update the description of the feature        
    }
  }

  /* Operational states */

  augment "/rt:routing"
        + "/rt:control-plane-protocols/rt:control-plane-protocol"
        + "/isis:isis/isis:interfaces/isis:interface"
        + "/isis:adjacencies/isis:adjacency" {
    when "derived-from-or-self(../../../../../rt:type,"
       + "'isis:isis')" {
      description
        "This augments IS-IS routing protocol structure, when used.";
    }
    description
      "This augments IS-IS protocol data nodes with SR.";
    uses adjacency-state;
  }

  augment "/rt:routing"
        + "/rt:control-plane-protocols/rt:control-plane-protocol"
        + "/isis:isis/isis:database/isis:levels/isis:lsp"
        + "/isis:router-capabilities" {
    when "derived-from-or-self(../../../../../rt:type,"
       + "'isis:isis')" {
      description
        "This augments IS-IS routing protocol structure, when used.";
    }
    description
      "This augments IS-IS protocol LSDB router capability.";
    uses sr-capability;
    uses sr-algorithm;
    uses srlb;
    uses srms-preference;
  }

  augment "/rt:routing"
        + "/rt:control-plane-protocols/rt:control-plane-protocol"
        + "/isis:isis/isis:database/isis:levels/isis:lsp"
        + "/isis:extended-is-neighbor/isis:neighbor" {
    when "derived-from-or-self(../../../../../../rt:type,"
       + "'isis:isis')" {
      description
        "This augments ISIS routing protocol structure, when used.";
    }
    description
      "This augments IS-IS protocol LSDB neighbor.";
    uses adjacency-segment-id;
  }

  augment "/rt:routing"
        + "/rt:control-plane-protocols/rt:control-plane-protocol"
        + "/isis:isis/isis:database/isis:levels/isis:lsp"
        + "/isis:mt-is-neighbor/isis:neighbor" {
    when "derived-from-or-self(../../../../../../rt:type,"
       + "'isis:isis')" {
      description
        "This augments IS-IS routing protocol structure, when used.";
    }
    description
      "This augments IS-IS protocol LSDB neighbor.";
    uses adjacency-segment-id;
  }

  augment "/rt:routing"
        + "/rt:control-plane-protocols/rt:control-plane-protocol"
        + "/isis:isis/isis:database/isis:levels/isis:lsp"
        + "/isis:extended-ipv4-reachability/isis:prefixes" {
    when "derived-from-or-self(../../../../../../rt:type,"
       + "'isis:isis')" {
      description
        "This augments IS-IS routing protocol structure, when used.";
    }
    description
      "This augments ISIS protocol LSDB prefix.";
    uses prefix-sid-sub-tlv;
  }

  augment "/rt:routing"
        + "/rt:control-plane-protocols/rt:control-plane-protocol"
        + "/isis:isis/isis:database/isis:levels/isis:lsp"
        + "/isis:mt-extended-ipv4-reachability/isis:prefixes" {
    when "derived-from-or-self(../../../../../../rt:type,"
       + "'isis:isis')" {
      description
        "This augments IS-IS routing protocol structure, when used.";
    }
    description
      "This augments ISIS protocol LSDB prefix.";
    uses prefix-sid-sub-tlv;
  }

  augment "/rt:routing"
        + "/rt:control-plane-protocols/rt:control-plane-protocol"
        + "/isis:isis/isis:database/isis:levels/isis:lsp"
        + "/isis:ipv6-reachability/isis:prefixes" {
    when "derived-from-or-self(../../../../../../rt:type,"
       + "'isis:isis')" {
      description
        "This augments IS-IS routing protocol structure, when used.";
    }
    description
      "This augments IS-IS protocol LSDB prefix.";
    uses prefix-sid-sub-tlv;
  }

  augment "/rt:routing"
        + "/rt:control-plane-protocols/rt:control-plane-protocol"
        + "/isis:isis/isis:database/isis:levels/isis:lsp"
        + "/isis:mt-ipv6-reachability/isis:prefixes" {
    when "derived-from-or-self(../../../../../../rt:type,"
       + "'isis:isis')" {
      description
        "This augments IS-IS routing protocol structure, when used.";
    }
    description
      "This augments IS-IS protocol LSDB prefix.";
    uses prefix-sid-sub-tlv;
  }

  augment "/rt:routing"
        + "/rt:control-plane-protocols/rt:control-plane-protocol"
        + "/isis:isis/isis:database/isis:levels/isis:lsp" {
    when "derived-from-or-self(../../../../rt:type,"
       + "'isis:isis')" {
      description
        "This augments IS-IS routing protocol structure, when used.";
    }
    description
      "This augments IS-IS protocol LSDB.";
    container sid-binding-tlvs {
      //Med: avoid repeating the parent node prefix
      list sid-binding {
        key "prefix";
        uses sid-binding-tlv;
        description
          "SID/label binding TLV, type 149.";
      }
      description
        "List of sid/label binding TLVs.";
    }
    container mt-sid-binding-tlvs {
      //Med: No need to repeat the parent prefix here.
      list mt-sid-binding {
        key "prefix mt-id";
        uses sid-binding-tlv;
        leaf mt-id {
          type uint16;
          description
            "A 12-bit value containing the non-zero ID
             of the topology.";
        }
        description
          "Multi-Topology SID/Label binding TLV, type 150.";
        reference
          "RFC 8667: IS-IS Extensions for Segment Routing,
                     Section 2.5";
      }
      description
        "List of multi-topology SID/Label Binding TLVs.";
    }
  }
}
